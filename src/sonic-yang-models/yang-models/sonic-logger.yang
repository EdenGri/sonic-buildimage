module sonic-logger{

    yang-version 1.1;

    namespace "http://github.com/Azure/sonic-logger";
    prefix logger;

    import sonic-types {
        prefix stypes;
    }

    description "Logger Table yang Module for SONiC";
    
    typedef swss_loglevel {
        type enumeration {
            enum EMERG;
            enum ALERT;
            enum CRIT;
            enum ERROR;
            enum WARN;
            enum NOTICE;
            enum INFO;
            enum DEBUG;
        }
    }
    
    typedef sai_loglevel {
        type enumeration {
            enum SAI_LOG_LEVEL_CRITICAL;
            enum SAI_LOG_LEVEL_ERROR;
            enum SAI_LOG_LEVEL_WARN;
            enum SAI_LOG_LEVEL_NOTICE;
            enum SAI_LOG_LEVEL_INFO;
            enum SAI_LOG_LEVEL_DEBUG;
        }
    }
    
    container sonic-logger {

        container LOGGER {

            description "Logger table in config_db.json";

            list LOGGER_LIST {

                key "name";

                leaf name {
                    description "Component name in LOGGER table (example for component: orchagent, Syncd, SAI components).";
                    type string;
                }

                leaf LOGLEVEL {
                    description "The log verbosity for the component";
                    mandatory true;
                    type union {
                        type swss_loglevel;
                        type sai_loglevel;
                    }
                }

                leaf LOGOUTPUT {
                    type enumeration {
                        enum SYSLOG;
                        enum STDOUT;
                        enum STDERR;
                    }
                    default SYSLOG;
                }  
            }
            /* end of list LOGGER_LIST */
        }
        /* end of LOGGER container */
    }
    /* end of sonic-logger container */
}
/* end of sonic-logger module */
